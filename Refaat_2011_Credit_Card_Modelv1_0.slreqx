# Refaat_2011_Credit_Card_Modelv1_0

## Refaat 2011 Credit Card Modelv1.0: References to Refaat 2011 Credit Card Modelv1.0.docx (Container)
Read-only references to Microsoft Word document.

### Data Preparation (Functional)

#### Data Sources (Functional)
Data Sources
The dataset for this example model is taken from [Refaat 2011]. The dataset seems to be randomly generated, or partially real but anonymized. The dataset has only 1200 rows. As the dataset is public for fair use, it is appropriate for examples for credit scoring models.

#### Model Development Population (Functional)
Model Development Population
Due to the small size of the dataset, all samples are utilized in model development, as well as for validation.

#### Risk Drivers (Functional)

##### Target Output (Functional)
Target Output
The target output of the model is an estimation of the probability of default. The dependent variable to train the model is the actual default flag which is denoted by the status variable in the dataset.

##### Imputation (Functional)
Imputation
A separate bin is created for missing data values.

##### Preprocessing (Functional)
Preprocessing
During the preprocessing phase, preprocessing of numeric predictors consists in applying equal frequency binning, with the initial number of bins set to . The preprocessing of categorical predictors consists in sorting the categories according to the 'SortCategories' criterion (the default is to sort by odds in increasing order). Sorting is not applied to ordinal predictors.

### Appendix (Functional)
