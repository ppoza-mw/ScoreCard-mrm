# model_development_standard

## #1: Introduction (Container)

### #2: Objectives (Informational)
Model risk is managed with other risks in the risk taxonomy. Model risk is managed with the Model Risk Management Framework (MRMF). The MRMF comprises policies, processes and tools to manage model risk. The scope includes model governance, risk policies and procedures, roles and responsibilities, internal audit, the model inventory, documentation and reporting.
Models should be fit for purpose. The requirements for model developers are described in this document.

### #3: Related documents (Informational)
The Model Risk Policy (MRP) is the main policy in the MRMF. This standard is a child policy of the MRP. The other two standard child policies of the MRP are the Model Validation Standard and the Model Governance Standard.
Specific regional requirements, e.g. in North America, to comply with SR11-7, must comply with the requirements in the MRP and child standards.

### #4: Exceptions (Informational)
Some of the requirements are not applicable for:
- EBA stress testing models
- Requests from the ECB for ICAAP and ILAAP.
- Rationale: EBA stress test models should adhere to the methodology prescribed by the EBA. The methodology changes for each stress test and may not be available in a suitable timeline to comply with the full model development standard. ECB requests may need to responded to within weeks, which is too short a timeline to follow the regular process.

### #5: Model types currently in scope (Informational)

#### #6: Risk models (Functional)

##### #7: Credit risk models (Functional)
- Probability of Default (PD)
- Loss given Default (LGD)
- Exposure at Default (EAD)
- Counterparty Credit Risk (CCR)

##### #8: Market risk models (Functional)
- Value at Risk (VaR)
- Incremental Risk Charge (IRC)

##### #9: Interest rate risk models (Functional)
- Equity at risk
- Income at risk
- Behavioural models

##### #10: Operational risk models (Functional)
- Compliance
- Anti Money Laundering (AML)

##### #11: Liquidity and funding risk (Functional)
- Funds Transfer Pricing (FTP)

#### #12: Capital models (Functional)
Capital models measure and aggregate risk with loss absorbing capital estimates. Capital models are commonly based on risk type models either for regulatory capital (RC) or business steering.

#### #13: Stress testing models (Functional)
Stress testing models for capital or other risk measures that identity risks not covered otherwise, for internal risk management or regulatory purposes, e.g.
Internal Capital Adequacy Assessment Process (ICAAP). Internal Liquidity Adequacy Assessment Process (ILAAP), European Banking Authority (EBA)
stress test, Dodd Frank Act. Stress Test (DFAST).

#### #14: Risk based performance assessment models (Functional)
- Risk adjusted return on capital (RAROC)

#### #15: Pricing models (Functional)
Pricing models that are used for valuation of f‌inancial products. They also feed into market risk models.

#### #16: Product advisory models (Functional)
Models that measure risk and return for clients.

### #18: Key definitions (Informational)

#### #19: Model definition (Functional)
A model is a quantitative method. system, or approach that applies statistical. economic, f‌inancial, or mathematical theories, techniques, and assumptions to process input data into quantitative estimates.
- Rationale: This definition potentially covers a wide range of models used for various purposes (including but not limited to analyzing business strategies, informing business decisions, identifying and measuring risks, valuing exposures, instruments or positions, conducting stress testing, assessing capital adequacy, managing client assets and meeting financial or regulatory reporting requirements).
  A model can consist of components, where each separate component could fit the above basic model def‌inition and thus would theoretically be a separate model. Conversely, a collection of models could constitute a new model. Partitioning the collection of all models into a unique collection of models is a matter of professional judgment and must be guided by prescribed model granularity principles.

#### #20: Model life cycle (Functional)
The model life-cycle (MLC) is a sequence of phases where all models go through. At a high level the model life-cycle consists of the following phases:
- Concept & planning phase
- Development phase
- Validation and approval phase
- Implementation and use phase
- Model retirement
- Rationale: During the use phase monitoring and review of the model take place. Note that the life cycle is not a linear sequence, models can re-visit previous phases for example in case of a periodic validation.

#### #25: Model management (Functional)
Model management consists of managing model risk and to manage the benefits and opportunities that models can bring. Hence, model management considers both the risk and return perspective. On the risk side it is important to manage model risk across the model life cycle as to ensure all model risk aspects are covered. This is in scope of the MRMF. On the return side it is important that the MLC phases result into models that are f‌it for purpose and optimally contribute to the business needs. However, managing model return is not the objective of the MRMF. Still, the model risk and model return side must both be managed. These two perspectives come together in the role of the model owner who has to oversee the balance between model risk and return and these risks and returns can be managed through the MLC.

## #21: Model Ownership (Container)
The role and responsibilities from a model risk perspective for model owners is described in the MRP. The responsibilities of the model owner reach further than only managing model risk. Therefore. a key assumption underlying the Model Development and Ownership Standard is that the model owner role includes the following tasks:
- Rationale: The formal approval of a (re)deve|oped model, continued model use after periodic review or the decision for model retirement remains the accountability of the designated committee.
  Model owners are encouraged to setup a MLC framework in terms of the sequence of various process steps, roles and responsibilities including business involvement to ensure models will optimally contribute to the business needs while also satisfying the MRMF requirements. It is up to the Model Owner to set up a MLC framework and decide how such MLC framework for their specific model type should be def‌ined. This is outside the MRMF scope as long as MRMF requirements are satisf‌ied.

### #22: Overall quality (Functional)
The Model Owner (MO) is accountable for the overall quality of the model for all phases of the model life-cycle (MLC). The MO is the continuous factor during the model life-cycle and must therefore oversee all phases. This is in contrast to the phases in isolation. where for each phase there can be a specif‌ic team in the lead for the execution. E.g. modelling team for model development, validation learn for validation, etc.

### #23: Model Risk and Model Return Balance (Functional)
The Model Owner should manage the balance between model risk and model return during the model life-cycle. In other words, e.g., while creating a model or using a model, then the MO is expected to take the lead in balanced decision making, taking into account dimensions such as model risk, modelling cost, time lines, business needs and regulatory expectations.

## #24: Model Development (Container)

### #28: Concept & planning phase (Functional)
1. Model owners and/or users express needs and requirements for new or existing models.
2. MD assesses the needs and requirements and decides to take on the development of a new model or redevelopment of an existing model.
3. MD typically def‌ines one or more concepts that could fulf‌il these needs and requirements.
4. MD creates a development plan which documents above steps and development planning.
- Rationale: In the Concept & Planning phase the objective is to understand the needs for the development of a new model, catch these needs into a clear and non-ambiguous model purpose and model requirements and capture these and other essential aspects of the model and model development in the Model Development Plan (MDP).

#### #33: Need for a new model (Functional)
The concept and planning phase must start with future owners, users or regulators expressing (changed or additional) need(s) to the model developer for which a new model may be required or an existing model may need to be redeveloped or changed.
- Rationale: The need to develop. redevelop or change a model. or. in some cases. purchase models may arise under a number of circumstances. including:
  1. Additional user needs for existing models; this may require model modif‌ication through re-design and re-development. or development of a new model.
  2. A new business need for products or services requiring new model development.
  3. Changes in the f‌inancial. regulatory, economic. market or business environment. These could lead to additional or new needs and subsequent re-development, or development. of a new model.
  4. Shortcomings of existing models, identif‌ied by either validators, developers or users.
  5. Renewed insight in modelling techniques or a change in modelling best practices.
  6. Changes in IT systems.
  7. Consolidation or expansion on of the overall use of models, e.g., reduction of complexity in the model landscape.
  In all cases the model development needs to start with future owners or users expressing their need for a new model or model changes/redevelopments to the model developer.

#### #34: Model purpose and requirements (Functional)
The model purpose and requirements must be explicitly and clearly defined and documented in the MDP.
Requirements must. be verif‌iable and/or testable. For new models. MD must communicate the model purpose to MV as soon as it is explicitly and clearly def‌ined.
- Rationale: The model development process starts by understanding what the model purpose should be in satisfying the needs of future owners, users and regulators. Together with the model purpose, clear and non-ambiguous model requirements that support this purpose need to be specified. For meeting this objective model users are encouraged to use the experience and expertise of MD and attention points from past model development processes. Also iterative sessions between MD and model users may be required before the model purpose and requirements are fully clear. The model purpose and requirements need to be documented in the Model Development Plan (MDP). For non-material redeveloprnents of existing models. a MDP is not required.

##### #35: Model performance requirements (Functional)
Measures for model performance need to be defined in the MDP.
- Rationale: Performance requirements should consider characteristics such as sensitivity to inputs, stability, accuracy, precision and uncertainty. Tests that evaluate acceptable ranges of model outcomes should be outlined. In addition, for statistical models these characteristics should include predictive power and for credit and capital models they could include the level of conservatism.

##### #36: Data requirements (Functional)
The MDP must take the data quality into account. It has to outline which data will be used and needs to clarify who is responsible for delivering this data. The MDP has to give an overview of the data quality of the source, e.g. data dimensions like completeness and accuracy of the data.
- Rationale: The data requirements need to be specif‌ied as much as possible during this phase in order to have an overview of the data quality issues that might exist. The people responsible for delivering the data will have the best understanding of possible quality issues.

##### #37: Environmental requirements (Functional)
Requirements with respect to the environment must cover the financial, regulatory. market, economic, and business environment.
- Rationale: The following are guidelines on topics to consider as part of the environment requirements:
  1. Requirements for the regulatory environment should consider the relevant and applicable regulations. by referencing to rules and restrictions relevant to the model. Whether the model will be used for regulatory reporting and/or which components of the model are predef‌ined by regulation, if any.
  2. Requirements for the economic environment should consider, for example, whether outputs should take economic conditions into account, such as, through-the—cycle vs. point in time estimates, and under what type of (stressed) economic conditions the model should be tested. Requirements for the financial environment mainly refer to rules and rates used for valuation purposes. for example. any accounting rules to be considered in the model. discounting rates. definition of f‌inancial ratios, f‌inancial units. including currencies. and any additional f‌inancial conventions. such as day count conventions.
  3. Requirements for the market environment. should consider characteristics of financial markets like liquidity, volatility or correlation scenarios within which the model is expected to operate. Furthermore, the requirements should def‌ine any specif‌ic market data to be used within the model and the relevant and applicable market conventions.
  4. Requirements for the business environment should consider applicable business activities for which the model will be used. Business requirements are closely related to the model use requirements.
  Note that the above areas are not disjoint and a certain variable used within a model can lie at the intersection of multiple environments.

##### #38: Use requirements (Functional)
Model use requirements must describe the business process the model is used in. by which business units the model is used and for which portfolios.
For models used by a different party than the developer the requirements must define how the model needs to be embedded. and a plan on the type of training and documentation that will be provided to model users where applicable.

##### #39: Alternatives to model development (Functional)
For a new model, MD must assess the need and take a decision on development based on the model purpose and requirements. This assessment must consider whether a model could and should be developed to meet these requirements or whether alternatives to rnodei development may be more effective in meeting the user needs.
- Rationale: New needs or new model requests shouldn‘t automatically result in the development of a new model as development. validation and maintenance of models can have large opportunity costs. MD should therefore assess whether the model development has added value or whether needs can be satisf‌ied in alternative ways. If the assessment has a negative outcome no development takes place.

#### #40: Concept defintion (Functional)
For a new model, a concept must fulfil all user requrrements and define:
1. In case of model (re)development where the methodology is not (fully) prescribed by the regulator: an appropriate theoretic framework , i.e. the reasoned proposal for the model design and construction, including where possible with reference to published research and/or internal documentation. The judgement includes a comparison of alternative theories and approaches if applicable.
2. Key assumptions, expert judgements and anticipated model limitations.
3. Data sources that. will be used for model development and any known issues and limitations for these data sources.
When during model development it turns out that requirements could not be met. this should be clearly stated and explained in the f‌inal model documentation.

##### #41: Development categories for new models (Functional)
1. New models for which the methodology is not (fully) prescribed by the regulator and for which alternative methodologies exist which have not been used or explored in earlier model developments by the associated MD team and for which no suitable external research is available. For these models at least one alternative concep must be explored. i.e. for other possible alternative(s) the pros and cons are listed. The reasoning for choosing the proposed methodology is written down. Development of a model concept must start by setting out the criteria and their relative importance by which a concept is assessed.
2. New models for which only one methodology exists which has not been used or explored in earlier model developments by the associated MD team. For these models argumentation must be provided why only one methodology is applicable.
3. New models based on methodologies that have been used or explored in earlier model developments by the associated MD team. For these models. reference to documentation on the use or exploration of these methodologies should be provided.
- Rationale: To ensure and enable effective challenge for developments in category 1. at least two or more concepts should be explored and a trade-off should be made by considering the following criteria:
  1. Development effort or cost
  2. Operational cost
  3. IT system resources
  4. Data quality and availability
  5. Familiarity (of staff) with modelling theory
  6. Availability of existing components
  7. Overall complexity
  If the trade-off cannot be made during the concept phase due to insufficient information on these criteria, the concepts should be continued in the development phase until sufficient information becomes available to make the trade-off. The above mentioned criteria should also be considered if the choice is made to build, buy or re-use the model.
  It could be that the consideration of alternatives is covered per model type and that, for a specif‌ic model, documentation simply refers to a separate study of these alternatives.

#### #42: Model hierarchy and grouping (Functional)
The model hierarchy and grouping for models need to be specifed during the concept & planning phase, which includes the model inputs, components. groupings and model type.
- Rationale: The model hierarchy and grouping refer to the structure in which models are embedded in the model landscape.
  Model hierarchy: Is the model a componet or an input model for other models and does itself have component models or input models.
  Model groupings: A collection of models that belong together, due to a similar design or a logical relationship in terms of model application. Teams can use their own terminology, like model families, categories and clusters, for types of groupings. Note that one model can be a part of several model groupings.
  There exist special and generic sort of model groupings that are very broadly used within the bank for communication and reporting purposes, the model type and application are two important cases.
  For a transparent model classif‌ication and communication. it. is advised to construct model naming going forward based on the model type, main application of the model and the model version.

#### #43: Model development plan (Functional)
As final deliverable for the Concept & Planning phase. MD must create a Model Development. Plan (’MDP’) that documents for High, Medium and Low model risk models:
1. Model purpose;
2. Model requirements;
3. Development milestones and related timing;
4. Initial determination of the model risk rating.
Other topics that can be added when deemed necessary are:
1. One or more model concepts or proposed model changes;
2. A high level test plan that defines tests for quantitative requirements. where possible. and acceptable outcome ranges:
3. Human resources:
4. System resources. e.g., software packages. database.
5. An overview of model stakeholders and dependencies with other models.
- Rationale: The MDP is the final deliverable in this phase and needs to be communicated to MV and be approved by the designated committee before the actual model development can be initiated. An initial draft of the MDP may be used to communicate the model purpose to MV.
  Examples of human resources are personnel involved to develop, test. document and implement, including developer resources, IT personnel. users. Subject Matter Experts (SMEs) and other stakeholders.

##### #44: Approval (Functional)
To enable an efficient process for risk models, the MDP must be approved by the designated approval committee as defined in the MRP.
- Rationale: In case of f‌inal rejection, MD either halts development or revises the concept and/or MDP. After approval of the Model Development Plan (MDP). MD starts to design and develop the model, or in the case of a vendor model the acquisition of the model.

### #29: Development phase (Functional)
1. MD designs and codes the model.
2. MD tests whether the model fulfils all requirements.
3. MD documents the model development steps, alternatives considered, testing results, assumptions. limitations and restrictions. and potentially newly discovered requirements or any requirements that could not. be satisfied.
4. MD interacts with model owners and/or users to verify that the model satisf‌ies the user needs and requirements.
Steps are repeated until the model fulf‌ils the modelling needs and requirements. If the model is ready, it is submitted for validation and approval.
- Rationale: Some iterations may take place. until the model fulfills all requirements. as described in the MDP. or the conclusion is reached that requirements cannot be met. During development additional methodological choices may need to be made on points that were not considered in the MDP.

#### #45: Data availability and quality (Functional)
Data sources, transformations. use and storage must be explictly identified and sufficiently described in the documentation so that an informed third party with
access to the data sources can use the above components for model output replication to a sufficient level of accuracy. Data sets used in development should be frozen and stored such that this data cannot be accidentally altered. This requirement applies to both the bank’s internal as well as external data.
For changes to ST due to EBA this can be performed after submission of the EBA ST results
- Rationale: Availability of good quality data is a necessary pie-condition for data driven model development and adequate model performance. Some data requirements for the concept and planning phase already need to be incorporated in the MDP. This subsection therefore covers specif‌ic requirements and guidance on data as used in the development phase.
  It‘s important that development data remains retrievable such that model output can be fully replicated. This holds for both the raw and the transformed data used in model development. Note that some (economic) indices will alter through time and some data is externally purchased, as a result. model documentation should store a fixed copy of the data and note retrieval date and time (e.g. through use of a timestamp) for replication purposes.
  When adapting and enhancing data the rationale and methods used should be clearly explained and documented. The effects of any adaptations should be analyzed and reported. Data use should cover how the transformed data was used in development. Data adjustments to improve data quality should be discussed with relevant stakeholders within the bank to contribute to data quality improvement beyond the specific case at. hand. Proxies that are used to replace or supplement data, such as industry data. should be carefully identified and justified.
  If data is not (fully) representative of the portfolio or characteristics of the intended business. these issues should be properly tracked and analyzed so that users are aware of potential limitations.

#### #46: Model processing (Functional)

##### #47: Sound design, theory and logic of the model (Functional)
The design. theory, and logic underlying the model must be well documented and, where possible, supported by published research, sound industry practice and/or internal documentation. The model methodologies and processing components that implement the theory, including the mathematical specif‌ication and the numerical techniques and approximations, tnust be explained in detail with particular attention to merits and limitations.
For changes to ST due to EBA: the changes to the existing framework should be listed and reasoning for this choice should be added. This can be performed after submission ofthe EBA stress test results.
- Rationale: The way in which data is processed into business information lies at the core of the modelling process and needs to be done in a conceptually sound way. This requires the design, theory and logic of the model to be consistent with published research and industry best practices.

###### #48: Selection of economic drivers or risk indicators (Functional)
When selecting economic drivers or risk indicators in a model each driver and/or indicator must be clearly def‌ined. It must be made clear why the variable is selected to be part of the model. based on a theoretic or environmental, e.g. economic or financial, rationale. Its unit and transformation (e.g. absolute. year-on-year change) and suitable data sources must also be def‌ined.
- Rationale: Through selection of economic drivers or risk indicators it is determined what kind of data impacts model outcomes. It needs to be ensured that the right economic drivers or risk indicators are selected. Selection of too few economic drivers or risk indicators can lead to an oversimplified model that is unable to describe the complexities of the real world, while inclusion of too many can make the model less intuitive and lead to overfitting in statistical models.

###### #49: Sensitivity analysis (Functional)
Where appropriate to the particular model and input variable, sensitivity analysis in model development and verification must be employed to check the impact of small changes in inputs and parameter values on model outputs to make sure they fall within an expected range.
- Rationale: For all economic drivers or risk indicators the following issues should be considered:
  - Sensitivity of model output with respect to each variable or a certain combination of variables.
  - Accuracy, and, for statistical models, contributions to the predictive and discriminatory power;
  - Contributions to the precision in litre with expected range of model outputs;
  Stressing model inputs should check performance over a wide range of inputs and parameter values, including extreme values. to establish the boundaries of model performance by identifying the acceptable range of inputs as well as conditions under which the model may become unstable or inaccurate.
  Model results, especially predictive outcomes, are never fully accurate. When possible, potential model error should also be estimated, typically with a conf‌idence interval. Efforts should be made to determine a best estimate for expected accuracy and precision.

###### #50: Model conservatism (Functional)
Conservatism in the model outcomes of capital models must be explicitly identif‌ied, justified, and. where possible, estimated. It. must also be made clear under which conditions. if any. conservatism can be removed. Conservatism in the model outcomes must be communicated to relevant stakeholders. e.g. owners of models that use the output.
Note that some models use other models as input (e.g. stress testing). If model A is input for model B. the analysis of the conservatism of model A should be made available by the involved model developer to the model developer of model B.
- Rationale: For credit risk and capital models, if it is not feasible to improve accuracy, it is considered prudent, where allowed by regulation, to aim for a conservative model outcome.
  Similar to adjustments to model outputs, adjustments to inputs and/or modelling choices and assumptions should be carefully identified, quantif‌ied and documented.

###### #51: Expert judgment (Functional)
There may be specif‌ic cases where expert judgement is needed because not enough data has yet been collected to quantitatively support modelling choices. In these cases. it must be made clear when enough data is expected to become available and when the qualitative expert judgement can be replaced with quantitative analysis.
Where involved, expert judgement must be conducted in an appropriate, systematic manner, which is thoroughly documented, for instance. by means of minutes of expert sessions. which include the opinion of the experts and substantiation for this. Note that in case of processes where timelines are short for ST models, it is suff‌icient to let experts sign-off on the model choices.

##### #52: Assumptions and Limitations (Functional)
Although model assumptions and limitations may have been considered and examined as a part of the requirements in the previous section. it is valuable to group and document them in a single section of the documentation. This information is very valuable in the model monitoring and use.

###### #53: Assumptions (Functional)
Key model assumptions must be clearly identif‌ied and documented in a single. separately identif‌iable section within the model documentation. In defining the assumptions the following aspects must be considered: theoretical framework, expert judgement. data, and environment. Assumptions must also be checked for mutual consistency.
- Rationale: In def‌ining the assumptions and considering the above mentioned aspects, consider the following:
  - Theoretical framework: Identify and describe assumptions underlying the model’s theory that could introduce uncertainty into the model. If the model uses a theoretic framework which is new to the bank all key assumptions should be stated;
  - Data: lderrtify and describe assumptions that were made for any significant part of the data used in development;
  - Environment: Identify and describe assumptions with respect to the f‌inancial. economic. market and/or business environment.

###### #54: Limitations (Functional)
Models can have limitations. i.e. circumstances in which the model performance may not be adequate anymore. Limitations typically have to do with the validity of the model inputs/parameters.
Limitations must be explicitly identif‌ied, quantif‌ied where possible, and properly documented.

##### #55: Software Development (Functional)
Source code must be reliable, clear and traceable.
- Rationale: If model development and/or implementation require the development of new or updated software then this requirement applies.
  Reliability means that the methodology is correctly implemented. and implementation is robust. Checks on intermediate and end results within the code make it possible to check that the code is reliable.
  Clear code means that the code is set up in a structured and readable way. Writing efficient code can make code less readable. in such cases it is important that suff‌icient explanation is provided per unit of code. Another developer with suff‌icient knowledge of the environment should be able to understand the code and code structure. Characteristics of clear code are:
  - Source code contains comments that define and describe the role of classes, objects, object members, object methods. or ruore general variables and functions. The description def‌ines the relation to the formal/mathernatical model def‌inition. Object methods or functions also describe their goal and define their inputs and outputs.
  - Source code is constructed in a modular approach and follows the Don‘t Repeat Yourself (DRY) principle: every piece of code has a single, unambiguous. authoritative representation within the system/model.
  - Next to source code comments, there is a separate description of the overall software architecture and ideas behind it, followed by a more detailed description of the different components.
  Traceability implies that source code is subject to version control, where each committed version has meaningful comments. Version control allows for a traceable, controllable flow of development in which multiple developers can work in parallel.
  For environments that are widely used for building or implementing models. teams can further work out requirements and best. practices for software development per development environment.

###### #56: Separation of development and approved version (Functional)
To ensure the use of approved model versions only. there must be a clear separation between the model version under development and the approved version one used for implementation in production (operational) systems.
As an exception to this requirement: in case a validation and/or approval of a model is not possible before use due to regulatory (stress test) deadlines, an unapproved adjusted model version may be used in the production system, only if a validation and/or approval has already been planned. This model version should be separated from any other model versions in order to be able to replicate the model outcomes at a later time.
- Rationale: This is especially of concern in the case that model developers are also the models users and there is no clear separation between development and operational systems.

#### #57: Output testing (Functional)
Models must be tested in order to verify that they fulfil all requirements, i.e. requrrernents set in the MDP and additional requirements. and perforrn as
intended. Testing must include risks associated with:
1. The model's theoretical framework
2. Implementation
3. Model performance and sensitivity
These tests do not. have a simple pass or fail outcome. but require interpretation by the model developers. Testing activities should be appropriately documented.
- Rationale: Model output testing in the development phase is vital in assessrng whether the model satisfies all desired requirements, including the requirements set in the MDP. and is performing as intended. In case model outputs are used by other models, the results on these models should also be evaluated.

#### #58: Adequate documentation (Functional)
Key aspects and elements of model development must be properly, completely and accurately documented.
- Rationale: In the documentation the activities performed in the previous steps are captured.

##### #59: Replicability (Functional)
Documentation must be suff‌iciently detailed to allow a third party with the necessary knowledge. expertise and experience to replicate the model outputs to a suff‌icient level of accuracy.
- Rationale: The replicability condition means that the documentation contains suff‌icient details for a third party with suff‌icient knowledge on the topic to build a model that works largely the same as the original model. What level of accuracy is suff‌icient, is dependent on the model, model environment and requirements in the model use. For instance stress testing and capital models can have a rather high level of complexity (and therefore uncertainty) and the outcomes are not used as accurate estimations. Therefore if a third party would aim to replicate such a model based on the documentation. it cannot be expected to produce the exact same outcomes, however the outcomes shouldn't be too different. A principle that should at least be met is that model outcomes of a well replicated model should be suff‌iciently similar to the original. so that both models can‘t lead to signif‌icantly different decisions in use of the model results.

##### #60: Model development documentation package (Functional)
The model development documentation package must:
1. Clearly explain the methodology.
2. Make proper reference to bank documentation or references to reputable external documentation, e.g., peer-reviewed journals or proceedings, or academic text books. References must also include model documentation on re-used model components.
3. Clearly state and explain the model‘s purpose and intended use and make a clear connection between the model's purpose and the intended business need and regulatory environment where applicable.
4. Define model ownership.
5. Outline model limitations and restrictions
6. Data sources. transformations. use and storage
7. Explicitly state any expert judgement with corresponding documentation
8. Explicitly state assumptions and document them grouped into a single section. A brief discussron of the conditions in which these assumptions may no longer hold must be included and revisited when necessary.
9. Include available test reports both for development and implementation tests.
10. lnclude a regulatory checklist, where applicable.
11. Include a plan detailing frequencies and activities for model monitoring and review. For changes to ST due to EBA this can be performed after submission of the EBA ST results
In case a model is developed in line with a formal specif‌ied methodology that is approved by the designated committee, then those topics that are already covered in the generic methodology do not have to be repeated in the model development documents if both the following conditions are met:
1. The model documentation must make reference to the methodology document;
2. All aspects that are model specific, such as test results. must be covered in the model documentation at all times.

### #30: Validation & approval phase (Functional)
Any High priority findings from the validation that are approved by the designated approval committee need to be solved prior to use of the model, or in some cases shortly after being placed in use, as specif‌ied in the approval decision.
For validation performed by CMV or CALM an action plan should be proposed by the model owner/developer. which will be submitted to the committee at the same time as the model f‌indings (see procedure on observations and advice). This plan explains actions and/or mitigations that will be taken and is up for decision making by the committee.
- Rationale:
  1. MV validates the model.
  2. Based on reporting by MD and advice from MV. the model approval committee either accepts or rejects the model.
  3. Rejected models are re-developed. starting again in the concept & planning phase, or discarded
  After the development, each model will be validated, as required by the MRP and the Model Validation Standard (MVS‘). After validation the model is presented for approval to the designated model approval committee. Model development documentation and model validation results are used to inform the approval committee. Only approved models can be taken into use. Once the model is approved. it is implemented after which it enters the use phase. For some risk models. additional regulatory approval may be required.
  If the model is rejected by the designated approval committee, remediation of issues identified, including model redevelopment, takes place. Testing. validation. approval and implementation must be re-performed before the model can enter the use phase. Alternatively, modelling may withdraw the model altogether.

### #31: Implementation & use phase (Functional)
1. Approved models are implemented and, after implementation acceptance testing, taken into use.
2. During model use the model is periodically monitored, reviewed and validated. Periodic validation is followed by model approval.
3. If periodic monitoring, reviewing or validation indicates that the model no longer performs adequately a model re-development is started.
4. Models that are no longer needed are decommissioned.

#### #61: Implementation (Functional)
Development and approval is followed by model implementation. Development and implementation must be followed by a final round of implementation acceptance testing consistent with the MRP.
- Rationale: Concerning this requirement there are three possible scenarios:
  1. There is no clear separation between development and production systems.
  2. The model source code can be directly embedded into the production system. This calls for a new software release and a new installation or installation update.
  3. The model source code cannot be directly embedded into the production system. Modif‌ications or even a complete rewrite of the model code is necessary to make it compatible to the target operational system.
  In scenario I passing the earlier mentioned development tests merely means that the associated model software version is the de facto production system. Scenario 2 suggests installing the software developed in the development step onto production systems. The last scenario requires a full software development project targeted at the operational system. Often in this case, the software development is executed by an IT team separate from the model developers involved in the design phase. MD however remains accountable for this step and needs to def‌ine software specifications to be used by the software development. This would then also involve writing software specif‌ications that provide more detailed software requirements for implementation of the model by software developers, consistent with the MRP.
  In all cases implementation should be f‌inalized with a pre-def‌ined implementation acceptance test that covers all user requirements. In the case development and production system are the same, f‌inal testing may overlap or be identical to development testing. Failure of acceptance testing. may require re-implementation. or. in some cases. re-development. The test results and the final conclusion based on the test results must be documented and archived.
  Models implemented in spreadsheets or other applications not otherwise housed in production systems. create incremental model risk due to a potential for miscalculations due to insuff‌icient controls in place (version, access, change, etc.). This approach to development should either be avoided or measures should be taken to ensure these risks are suff‌iciently mitigated.

#### #62: Model Monitoring (Functional)

#### #63: Responsibility for monitoring (Functional)
After approval for use, the model must be monitored. MD is responsible for model monitoring unless imposed otherwise by regulation. Similar to review and validation, monitoring must be risk-based, i.e., monitoring planning and actions must be tailored to inherent model risk. For models with high risk extended monitoring rmrst be performed.
- Rationale: After approval for use and implementation, the model is taken into use and enters a process of monitoring. The monitoring of the model is the responsibility of the MD. Monitoring results must be documented and be communicated to MV.

#### #64: Monitoring plan (Functional)
Planning for monitoring. i.e.. frequency and tests performed by MD. is documented in a monitoring plan. The performance tests and their acceptable outcome ranges are also documented as part of the monitoring.
During the validation MD and MV will discuss the proposed monitoring plan and come up with the f‌inal monitoring agreements.
- Rationale: The monitoring frequency should generally be consistent with the frequency of model use on a logical aggregated level, e.g., portfolio or business unit, taking into consideration its assessed model risk, its purpose, environment, complexity and impact. At least the frequency required by relevant regulations, if applicable, must be retained.

#### #65: Scope of monitoring (Functional)
Model monitoring must cover the following elements:
1. Start simultaneous with start model use and perform periodically
2. Make use of one or more outcome analyses to periodically evaluate whether the model is being used correctly and is performing as intended.
3. Detect changes in the environment or in the model’s use that may necessitate changes in the model such as recalibration, modification. redevelopment. or replacement.
4. Check whether a model is being used beyond its limitations as either found by MD during development or by MV during validation.
5. Prornptly investigate indications of degraded model performance or failure and decide on model modification or other rnitigations.
6. Share the monitoring results with MV and notify MV on degraded performance or model failure. Notify the designated committee and the model owner at senior management level on indications of significant degraded model performance or failure.
- Rationale: Monitoring should also consider any patterns of qualitative adjustments by model users (i.e., ongoing adjustments in one direction could signal decline in model performance) and other indications of model weakness or bias beyond acceptable levels.

#### #66: Extended model monitoring (Functional)
Extended model monitoring must contain the following actions:
1. Analyse and explain model performance.
2. Verify that the model is still fit for purpose and meets its requirements.
3. Check if the model requires modification.
4. Report the results and share the report with MV

### #32: Model retirement (Functional)

## #67: Model Use (Functional)
- Rationale: After implementation the rrrodel is taken into use and is monitored by MD and is periodically reviewed by MV. Based on monitoring and periodic review results it is assessed whether the model still performs acceptably.
  During model use the risk of incorrect model use, also denoted as model risk type II in the MRP, arises. It is tirerefore important to set general model use requirements, make a distinction between different levels of model use and specify mitigation measures for each level.

### #68: General model use requirements (Functional)
Only approved models, consistent with the MRP, may be used.
For models that are already in use at the effective date of this standard and that are not approved, a validation and approval plan should be made to come to a state where all models are validated and approved.
Model changes to pillar 2 models due to EBA stress test or ICLAAP requests from the regulator can be used before approval, but need to be validated and approved after the ICLAAP or EBA stress test reports have been finalized.
- Rationale: Only models that have been validated and approved by the designated committee may be used.
  Depending on the type of model three levels of model use are distinguished:
  1. Developer models: The model developer is also the model user.
  2. Embedded models: The model user can’t interact with the model or select models, as it is integrated within a system. As such the user risk is limited, this level of model use is therefore not further discussed.
  3. End-user models: The model user interacts with the model. We can identify various users in this case:
  - Users that fill all required model inputs and provide data in order to run the model
  - Users that select to use a model, in case there are multiple possible models
  - Users can select methodology features, for example in certain pricing models users can select the number of simulations or interpolation

### #69: Model use requirements for developer models (Functional)
The following is required to manage the additional model-use-risk for developer models:
1. The team manager is accountable for access-control for model development and model use such that only authorized staff has access to the model.
2. The knowledge to operate the model such that it will be used as intended must be guaranteed.
3. Version Control: Developer models may only be used, if there is a mechanism in place which ensures that the used model is identical to the validated and approved model. In case of processes where timelines are short (i.e. ICAAP or ST requests from the regulator), model versions that are different from the validated and approved model may be used.
- Rationale: Developer models are models built and used by the model developer. The model developer can be an individual or a team of specialists. As the users have developed the model, no training in correct model usage is needed and the risk of incorrect use is limited. However as the model developers have access to the model coding and can change contents this leads to various risks:
  1. Model developers use versions in which they have made changes that haven’t been approved.
  2. Various users make unknowingly use of different model versions.
  An important requirement for developer models is therefore that there is a model version control.

### #70: Model use requirements for end-user models (Functional)
- Rationale: For end-user moclels, the model user is not the model developer, which makes it necessary to instruct the users on how to use the model and on limits and other restrictions that apply to the model. Incorrect model usage is mitigated for user models through four measures.

#### #71: Correct authorization (Functional)
For each end-user model, or system of end-user models, there rrrust be
1. A model use authorizer who is responsible for end-user model authorization for model use. The authorizer must be known once the designated committee approves the model. In general the authorizer will be the user’s line manager.
2. An approach in place by which users can be authorized access to models in the context of their roles and responsibilities.
3. A procedure in place to check periodically that the model usage has been in line with the roles and responsibilities of the end-users.
- Rationale: Only authorized users have access to and can make use of the model

#### #72: Adequate use manuals (Functional)
For end-user models there must be an user marrual available that adequately describes the intended usage of the model or number of related models. The user manual must at least address the following points:
1. Model Description: a description of the aspect of reality the model is considered to represent and a reference to the quantif‌ication it is specif‌ically built for.
2. Model Purpose and intended model application: a description of the context in which the model’s quantitative output may be used.
3. Model Input: For model input variables a clear description is available describing what input data is required.
4. Model Processing: In case a model can process input data into output data in alternative ways, by means of user def‌ined settings, then each (parameter) setting option and the consequence of a user def‌ined setting that the user is allowed to use, must be explained.
5. Model Output: The model output or model outputs must be described unambiguously. When applicable, the manual clearly def‌ines the situations where model output can be adjusted by human judgement procedures to perform that overriding.
- Rationale: There should be adequate use manuals in place that contain detailed instructions of how to use the model and which describes attention points.

#### #73: Adequate training (Functional)
Model users must have received adequate training before independently using models in the production environment.
- Rationale: Users must have received adequate training

#### #74: Model support function (Functional)
For each end-user model there must be a MSF available who can be contacted by the model end-user for assistance on proper model usage. The Model Support Function is responsible to inform model end-users about any limitations and any other restrictions. Model end-users are required to follow all guidance from the Model Support Function with respect to model limitations and restriction in the use of the models.
The MSF must periodically assess whether the model is used correctly and whether additional training or use documentation is necessary.
- Rationale: For end user models there should be people in place that can provide guidance and checks whether users adhere to limitations and any other restrictions. This function is generally performed by the assigned model owner or his or her desigrree.

## #75: Vendor Models (Functional)
- Rationale: The acquisition and use of vendor and other third-party models, i.e., models that are developed by entities outside the bank, require a different approach than internal model development. This is partly because the modeling expertise is external to the bank and not necessarily fully aligned with the bank's business needs. In addition, internal knowledge on the vendor model is limited due to its proprietary nature, which may increase model risk.
  As external parties might be less aware of the context in which the model will be used, corrrpared to internal model developers, there is a risk that the provided model doesn’t meet the user needs and requirerrrents. An explicit and clear def‌inition of user requirements is therefore of an even greater
  importance for vendor models.It is especially relevant for vendor models that users request assistance from MD in clearly defining the model purpose and
  requirements. The model needs to be customized and conf‌igured to the specif‌ic business needs or has to have sufficient f‌lexibility in order to allow the users to establish this themselves. It should be determined what type of instruction manuals and support is required from the vendor.
  In case of vendor system concept, the choice of how to put the model in place should consider development type. build. buy or re-use and be guided by the following criteria:
  1. Suitability. applicability, dependability and relevance of vendor solution to bank's portfolios or positions.
  2. Initial and ongoing cost of vendor solution. including supporting systerrrs, monitoring and maintenance cost.
  3. Transparency of the vendor’s solution. including the extent to which the vendor system is amenable to extension of capabilities and validation.
  4. Other elements of vendor management, such as any remedial capabilities in case of sudden contract terrrrirration.

### #78: Acquisition decision (Functional)
The acquisition decision of a vendor system rrrust take into account MV's advice on the vendor system‘s suitability to validation and the opinion of the designated model approval committee. prior to contracting with a vendor or otherwise committing to a vendor.
- Rationale: An additional requirement is that MV and the designated model approval committee need to be involved in the acquisition decision.

### #79: Accountability and responsibility (Functional)
MD is accountable and the vendor is responsible that vendor models embedded in vendor systerrrs are suitable for use and are f‌it for purpose.

### #80: Customization choices and development data (Functional)
The customization choices rrrust be documented and substantiated and serve as input for validation. Tire vendor must provide information regarding the data used to develop the model. MD must determine whether there are limitations to the model due to used data and its representative of the bank's situation Similar to in-house models, MD rrrust carry out monitoring and outcomes analyses of vendor model performance for as far as the accessibility and the methodology of the vendor model allow this.
- Rationale: The vendor must provide suff‌icient information regarding customization choices and development data.

### #81: Model knowledge (Functional)
MD must have detailed in-house knowledge of the vendor models and its capabilities. applicability, and limitations.
- Rationale: MD must have the necessary model knowledge in order to support model users and to carry out model monitoring and analyses of outcomes.

## #76: Model retirement (Functional)
Periodically. model owners and other stakeholders will reassess the need to continue to maintain each model. giving consideration to business need, incremental cost of model maintenance and model risk management and alternatives to model use. When model owners or other stakeholders decide that a
model is no longer needed the model owners propose to the designated committee that the model be retired and MV provides advice on the proposal to the committee. The commitee then decides if the model can be retired.
- Rationale: In case stakeholders of the model decide that the model is no longer needed, the model owners propose the retirerment to the designated committee and MV provides advice on this proposal to the committee. In case of retirement the model status in the Model Inventory is changed to retired.

## #77: Exception management process (Functional)
- Rationale: Requests for exceptions to requirements in this standard are approved by the designated approval committee on a case by case basis. Exceptions are granted by the committee based on facts and circumstances, including consideration for materiality. other mitigants, specific reasons why an exception is sought. and other factors. as applicable. Models are added to the inventory even when they fall under these exceptions. Exceptions must be reviewed by MD. MV and the designated approval commitee on a periodic basis, at least annually and more often when necessary.

## #82: Roles and responsiblities (Functional)

### #83: Model developers (Functional)
Tire primary role of model developers (MD) is model development. Model developers interact with:
- Subject matter experts (SME’s) from which they gain knowledge and obtain information on the model‘s subject.
- Model users. from whom they receive irrforrrratiorr on business needs that drive development. as well as specific user reguircments. and feedback on model use.
- Model validators. who they inform of planned model developments. provide with access to the model, data and documentation for validation purposes and interact with by responding to validation inquiries
- Model approval bodies, from whom they seek approval of validated models.

### #84: Model users (Functional)
Tire primary role of model users (MU) is to use the model for their business activities. In addition to developers. they also interact with model validators by responding to validation inquiries and providing feedback on model use. e.g., is the model performing as expected by the users. or is it malfunctioning.

### #85: Model validators (Functional)
The primary role of model validators (MV) is to validate models by evaluating the model aspects and elements according to the requirements in the MVS. In addition to developers and users, they also interact with the approval body by providing them with non-binding advice on model approval. In the MRP context the model validator is implied that is responsible for the validation of the corresponding model.
Model validators will be independent of:
- model developers
- model users
- other stakeholders that have an interest in model approval or model output

### #86: Model approval bodies (Functional)
The primrary role of model approval bodies is to decide on the approval of rrrodel use. guided by advice from model validators. In addition to developers and validators. model approval bodies interact with the Executive Marragement to whom they report on model risk management.

### #87: Executive management (Functional)
Executive Management has end-responsibility for model risk management. In addition to model approval bodies, they also interact with the Board and externally with regulators to whom they report on model risk management as part of the broader risk management framework.

### #88: Staffing (Functional)
Development staff must have suff‌icient knowledge, skills. and expertise to be able to develop the models and manage the model development projects that
fall under their responsibility and development ownership.
- Rationale: For technical developers. a high level of technical expertise is needed to cope with the complexity of relevant model types. both in structure and in application. An MSc or PhD degree in economics, econometrics, (f‌inancial) mathematics, physics, or engineering is typically required. Technical staff should have a good theoretical background in the discipline that is associated with the relevant model types, e.g., statistics, ecorrorrretrics, or financial mathematics, in combination with practical modelling and software development skills.
  To ensure a good understanding of business needs, development staff should have a significant degree of familiarity with the line of business using the designated models and their intended use. In addition, staff should also have a thorough understanding of regulatory requirements that are applicable to their
  domain. Critical and analytical thinking, creative problem solving and project management skills are core key competencies for development staff and should be assessed as such in staff performance management. Individual staff members should be able to operate effectively as part of the development tearrr. Staff should be continuously educated on technical model expertise and effective communication skills. e.g., documenting, reporting. or presenting.
  Model development should be executed by a relevant MD team. Because “ad hoc" model development by parties outside those in a full time MD role. potentially increases model risk, the designated approval committee should assess a proposed “ad-hoc” development team’s experience, skills and
  professional background for a given model.

## #90: Standard monitoring (Functional)
The requirements, roles and responsibilities as defined in this standard are managed, monitored and reported in the following way:
1. Operational Risk is the owner of this standard and is therefore accountable for monitoring that all stakeholders involved operate in accordance to this standard.
2. Model Risk Governance is responsible to oversee adherence to this standard.
3. Model Risk Governance will report standard compliance breaches directly to the head of MV and the issue is send for information to the f‌irst forthcoming meeting of the designated approval committee. This way head of MV and the committee(s) are informed in a timely manner and any standard compliancy breaches are included in the committee minutes and action list and tracked until they are solved.
